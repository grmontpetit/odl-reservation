// vi: set smarttab et sw=4 tabstop=4:
module butler-service-impl {

    yang-version 1;
    namespace "urn:opendaylight:params:xml:ns:yang:controller:config:butler-service:impl";
    prefix "butler-service-impl";

    import config { prefix config; revision-date 2013-04-05; }
    import rpc-context { prefix rpcx; revision-date 2013-06-17; }

    import opendaylight-md-sal-binding { prefix mdsal; revision-date 2013-10-28; }

    description
        "This module contains the base YANG definitions for
        butler-service impl implementation.";

    revision "2014-11-16" {
        description
            "Initial revision.";
    }

    // This is the definition of butler service interface identity.
    // It will be used by the config subsystem to advertise the service instance
    // provided by the butler-service-impl module as an OSGI service
    // with the ButlerService java interface.
    // Since we didn't make a yang data model for the butler, and we don't
    // advertise the ButlerServiceImpl with the MD-SAL service registry,
    // the only other way to access the ButlerService is by obtaining
    // it via OSGI.
    identity butler-service {
        base "config:service-type";
        // config:java-class property specifies the ButlerService java interface
        config:java-class "org.opendaylight.controller.butler.api.ButlerService";
    }

    // This is the definition of butler service implementation module identity. 
    identity butler-service-impl {
            base config:module-type;
            // refers to the butler-service identity
            config:provided-service butler-service;
            config:java-name-prefix ButlerService;
    }

    augment "/config:modules/config:module/config:configuration" {
        case butler-service-impl {
            when "/config:modules/config:module/config:type = 'butler-service-impl'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }
        }
    }
    
    augment "/config:modules/config:module/config:state" {
        case butler-service-impl {
            when "/config:modules/config:module/config:type = 'butler-service-impl'";
            
            //rpcx:rpc-context-instance "make-scrambled-with-wheat-rpc";
            rpcx:rpc-context-instance "make-black-tea-with-lapresse-rpc";
        }
    }

    identity make-black-tea-with-lapresse-rpc;

    rpc make-black-tea-with-lapresse  {
        description
          "Shortcut JMX call to serve a cup of tea with the newspapers";

        input {
            uses rpcx:rpc-context-ref {
                refine context-instance {
                    rpcx:rpc-context-instance make-black-tea-with-lapresse-rpc;
                }
            }
        }
        output {
            leaf result {
                type boolean;
            }
        }
    }
}
